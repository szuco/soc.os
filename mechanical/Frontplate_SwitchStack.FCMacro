# -*- coding: utf-8 -*-
"""
KiCad SwitchStack - Frontplatte fuer 55x55-Schalterprogramme, Version 2.
FreeCAD-Makro, getestet gegen die Part-Workbench-API (FreeCAD 0.21 / 1.0).

Design: rundes Display in der Mitte (ST77916 1,46", aktiv Ø37,25),
vier sichelfoermige Tastenkappen als Ringsegmente um das Fenster.

Erzeugt zwei Objekte: "Frontplate" (Platte) und "ButtonCaps" (4 Kappen in
Einbaulage). Fuer den Druck die Kappen separat exportieren.

Die Python-Variante mechanical/frontplate.py ist die geprueft Referenz;
dieses Makro dient dem interaktiven Weiterkonstruieren in FreeCAD.
"""

import math
import FreeCAD as App
import Part

# ---------------------------------------------------------------------------
# PARAMETER (identisch zu mechanical/frontplate.py)
# ---------------------------------------------------------------------------

PLATE_SIZE      = 54.6
PLATE_THICKNESS = 2.5
PLATE_CORNER_R  = 2.0

BOSS_SIZE       = 50.0
BOSS_WALL       = 2.0
BOSS_DEPTH      = 3.0

EAR_SPAN        = 76.0
EAR_WIDTH       = 14.0
EAR_THICKNESS   = 2.5
SCREW_PITCH     = 60.0
SCREW_SLOT_LEN  = 4.0
SCREW_SLOT_W    = 3.9

DISP_WINDOW_D   = 37.8      # ST77916 1,46"; aktiv 37,25
DISP_MODULE_D   = 41.5      # Modul-Aussen - AM REALEN TEIL MESSEN
DISP_CLEARANCE  = 0.5

KEY_SLOT_RI     = 22.0      # >= DISP_MODULE_D/2 + CLEARANCE + KEY_LIP
KEY_SLOT_RO     = 26.2
KEY_SPOKE_HW    = 4.5       # halbe Stegbreite (9 mm Stege auf 0/90/180/270)
KEY_GAP         = 0.25
KEY_PROUD       = 0.8
KEY_LIP         = 0.7
KEY_LIP_H       = 1.0
KEY_POST_D      = 2.2
KEY_POST_R      = 23.2      # begrenzt durch SMD-Taster auf dem Ø52-Board
KEY_POST_ANG    = 18.0
KEY_POST_LEN    = 4.0

STAR_EXIT       = True
STAR_EXIT_D     = 4.5
STAR_EXIT_Y     = -24.0

BACK = EAR_THICKNESS + BOSS_DEPTH
FULL = PLATE_THICKNESS + BACK
V = App.Vector


def centred_box(sx, sy, sz, z0):
    return Part.makeBox(sx, sy, sz, V(-sx / 2.0, -sy / 2.0, z0))


def rounded_plate(size, thickness, radius, z0):
    box = centred_box(size, size, thickness, z0)
    vertical = [e for e in box.Edges
                if abs(e.Vertexes[0].Point.z - e.Vertexes[-1].Point.z) > 1e-6]
    return box.makeFillet(radius, vertical)


def ring_segments(ri, ro, spoke_hw, z0, h):
    """Ring ri..ro, unterbrochen von Stegen auf den Achsen ->
    vier Segmente auf den Diagonalen."""
    ring = Part.makeCylinder(ro, h, V(0, 0, z0), V(0, 0, 1)).cut(
        Part.makeCylinder(ri, h + 2.0, V(0, 0, z0 - 1.0), V(0, 0, 1)))
    sp1 = centred_box(2 * ro + 4, 2 * spoke_hw, h + 2.0, z0 - 1.0)
    sp2 = centred_box(2 * spoke_hw, 2 * ro + 4, h + 2.0, z0 - 1.0)
    return ring.cut(sp1).cut(sp2)


def thru_cyl(radius, x, y):
    return Part.makeCylinder(radius, FULL + 2.0, V(x, y, -BACK - 1.0), V(0, 0, 1))


def slot(length, width, x, y, z0, height):
    r = width / 2.0
    body = Part.makeBox(width, length, height, V(x - r, y - length / 2.0, z0))
    c1 = Part.makeCylinder(r, height, V(x, y - length / 2.0, z0), V(0, 0, 1))
    c2 = Part.makeCylinder(r, height, V(x, y + length / 2.0, z0), V(0, 0, 1))
    return body.fuse(c1).fuse(c2)


def build_plate():
    shape = rounded_plate(PLATE_SIZE, PLATE_THICKNESS, PLATE_CORNER_R, 0.0)
    shape = shape.fuse(centred_box(EAR_SPAN, EAR_WIDTH,
                                   EAR_THICKNESS, -EAR_THICKNESS))
    outer = centred_box(BOSS_SIZE, BOSS_SIZE, BOSS_DEPTH, -BACK)
    inner = centred_box(BOSS_SIZE - 2 * BOSS_WALL, BOSS_SIZE - 2 * BOSS_WALL,
                        BOSS_DEPTH + 2.0, -BACK - 1.0)
    shape = shape.fuse(outer.cut(inner)).removeSplitter()

    # Modulfreiraum und Fenster
    shape = shape.cut(Part.makeCylinder((DISP_MODULE_D / 2.0 + DISP_CLEARANCE), BACK + 1.0,
                                        V(0, 0, -BACK - 1.0), V(0, 0, 1)))
    shape = shape.cut(Part.makeCylinder(DISP_WINDOW_D / 2.0, PLATE_THICKNESS + 2.0,
                                        V(0, 0, -1.0), V(0, 0, 1)))

    # Sichelschlitze durch die Platte
    shape = shape.cut(ring_segments(KEY_SLOT_RI, KEY_SLOT_RO, KEY_SPOKE_HW,
                                    -0.5, PLATE_THICKNESS + 1.5))

    # Freidrehung fuer die Kappenkragen (Ohren-Oberseite ausraeumen)
    relief = Part.makeCylinder(KEY_SLOT_RO + KEY_LIP + 0.6, KEY_LIP_H + 0.2,
                               V(0, 0, -(KEY_LIP_H + 0.2)), V(0, 0, 1)).cut(
        Part.makeCylinder(KEY_SLOT_RI - KEY_LIP - 0.6, KEY_LIP_H + 2.0,
                          V(0, 0, -(KEY_LIP_H + 1.0)), V(0, 0, 1)))
    shape = shape.cut(relief)

    # Geraeteschrauben
    for sx in (SCREW_PITCH / 2.0, -SCREW_PITCH / 2.0):
        shape = shape.cut(slot(SCREW_SLOT_LEN, SCREW_SLOT_W, sx, 0.0,
                               -EAR_THICKNESS - 1.0, EAR_THICKNESS + 2.0))

    # Stern-Kabelausgang durch den unteren Steg (kerbt bewusst den Kragen)
    if STAR_EXIT:
        shape = shape.cut(thru_cyl(STAR_EXIT_D / 2.0, 0.0, STAR_EXIT_Y))

    return shape.removeSplitter()


def build_caps():
    body_hw = KEY_SPOKE_HW + 2 * KEY_GAP
    lip_hw  = KEY_SPOKE_HW - KEY_LIP
    top_z   = PLATE_THICKNESS + KEY_PROUD

    body = ring_segments(KEY_SLOT_RI + KEY_GAP, KEY_SLOT_RO - KEY_GAP,
                         body_hw, 0.0, top_z)
    lip = ring_segments(KEY_SLOT_RI - KEY_LIP, KEY_SLOT_RO + KEY_LIP,
                        lip_hw, -KEY_LIP_H, KEY_LIP_H)
    caps = body.fuse(lip)

    for q in range(4):
        for da in (-KEY_POST_ANG, KEY_POST_ANG):
            a = math.radians(45 + 90 * q + da)
            x = KEY_POST_R * math.cos(a)
            y = KEY_POST_R * math.sin(a)
            caps = caps.fuse(Part.makeCylinder(
                KEY_POST_D / 2.0, KEY_POST_LEN,
                V(x, y, -(KEY_LIP_H + KEY_POST_LEN)), V(0, 0, 1)))

    return caps.removeSplitter()


doc = App.ActiveDocument or App.newDocument("SwitchStack_Frontplate")
for obj in list(doc.Objects):
    if obj.Name.startswith(("Frontplate", "ButtonCaps")):
        doc.removeObject(obj.Name)

plate = build_plate()
caps = build_caps()

f1 = doc.addObject("Part::Feature", "Frontplate")
f1.Shape = plate
f2 = doc.addObject("Part::Feature", "ButtonCaps")
f2.Shape = caps
doc.recompute()

common = plate.common(caps)
App.Console.PrintMessage(
    "Frontplate: %.2f cm3, %d Solid(s) | ButtonCaps: %.2f cm3, %d Solid(s) | "
    "Kollision Platte/Kappen: %.3f mm3 (soll 0)\n"
    % (plate.Volume / 1000.0, len(plate.Solids),
       caps.Volume / 1000.0, len(caps.Solids), common.Volume))

try:
    import FreeCADGui
    FreeCADGui.ActiveDocument.ActiveView.viewAxometric()
    FreeCADGui.SendMsgToActiveView("ViewFit")
except Exception:
    pass
